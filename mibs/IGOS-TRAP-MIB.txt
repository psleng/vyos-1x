IGOS-TRAP-MIB DEFINITIONS ::= BEGIN

    IMPORTS
            MODULE-IDENTITY, OBJECT-TYPE, NOTIFICATION-TYPE
                FROM SNMPv2-SMI
            MODULE-COMPLIANCE, OBJECT-GROUP
                FROM SNMPv2-CONF
            igos
                FROM IGOS-SMI
    ;

    igosTrapMIB MODULE-IDENTITY
           LAST-UPDATED "202609160000Z"
           ORGANIZATION "IGOS"
           CONTACT-INFO
           "IGOS (Perle iGOS) - https://igos.io"
       DESCRIPTION
          "The MIB module describing configuration-related traps
          emitted by an IGOS (Perle iGOS) system."
       REVISION "202609160000Z"
       DESCRIPTION
          "Rebranded from VYATTA-TRAP-MIB and re-rooted under the igos
           container { igos 2 } = .1.3.6.1.4.1.1966.30.2.  Object
           definitions are otherwise unchanged."
      ::= { igos 2 }


-- Trap Support Objects

mgmtTrap OBJECT IDENTIFIER ::= { igosTrapMIB 1 }
mgmtEventObjects OBJECT IDENTIFIER ::= { mgmtTrap 1 }
mgmtEvent OBJECT IDENTIFIER ::= { mgmtTrap 2 }

mgmtEventUser OBJECT-TYPE
    SYNTAX      OCTET STRING
    MAX-ACCESS  read-only
    STATUS      current
    DESCRIPTION
        "The user that initiated the event the trap is reporting."
    ::= { mgmtEventObjects 1 }


mgmtEventSource OBJECT-TYPE
    SYNTAX      INTEGER {
                 unknown (0),
                 firewall (1) }
    MAX-ACCESS  read-only
    STATUS      current
    DESCRIPTION
        "The source of the event the trap is reporting."
    ::= { mgmtEventObjects 2 }


mgmtEventType OBJECT-TYPE
    SYNTAX      INTEGER {
                 unknown (0),
                 added (1),
                 deleted (2),
                 changed (3) }
    MAX-ACCESS  read-only
    STATUS      current
    DESCRIPTION
        "The event type the trap is reporting."
    ::= { mgmtEventObjects 3 }


mgmtEventPrevCfg OBJECT-TYPE
    SYNTAX      OCTET STRING
    MAX-ACCESS  read-only
    STATUS      current
    DESCRIPTION
        "The previous configuration. This field is only valid
        for mgmtEventType deleted and changed."
    ::= { mgmtEventObjects 4 }

mgmtEventCurrCfg OBJECT-TYPE
    SYNTAX      OCTET STRING
    MAX-ACCESS  read-only
    STATUS      current
    DESCRIPTION
        "The current configuration. This field is only valid
        for mgmtEventType added and changed."
    ::= { mgmtEventObjects 5 }


-- Traps

    mgmtEventTrap NOTIFICATION-TYPE
        OBJECTS { mgmtEventUser,
                  mgmtEventSource,
                  mgmtEventType,
                  mgmtEventPrevCfg,
                  mgmtEventCurrCfg }
        STATUS  current
        DESCRIPTION
           "Notification of a configuration related event."
   ::= { mgmtEvent 1 }

END
