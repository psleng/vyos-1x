IGOS-SMI DEFINITIONS ::= BEGIN

-- ============================================================================
-- IGOS-SMI
--
-- Structure of Management Information for IGOS (Perle iGOS).
--
-- Defines the single root container node from which all IGOS-* enterprise
-- MIBs hang.  IGOS is allocated arc 30 under Perle Systems' IANA Private
-- Enterprise Number 1966, i.e.:
--
--     igos = .1.3.6.1.4.1.1966.30
--
-- Perle's own product/feature MIBs occupy 1966.{1,2,9-13,20-23}; arc 30 is
-- reserved here for the iGOS (VyOS-derived) additions so the two trees never
-- collide.  New IGOS MIBs register a child of { igos N }:
--     igosWwanMIB  ::= { igos 1 }
--     igosTrapMIB  ::= { igos 2 }
-- ============================================================================

    IMPORTS
        enterprises
            FROM SNMPv2-SMI
    ;

    igos OBJECT IDENTIFIER ::= { enterprises 1966 30 }

END
